# Гараж 61: онлайн-запись в автосервис: требования

# Specification: Гараж 61: онлайн-запись в автосервис

## SEC-BR: Бизнес-требования (SECTION)

### BR-001: Снизить долю неявок (REQUIREMENT)
Доля неявок клиентов должна снизиться с 15% до 7% записей в течение 6 месяцев после запуска системы.
- STATUS: reviewed
- PRIORITY: must
- GOAL: доля неявок от числа записей <= 7 %

### BR-002: Перевести запись в онлайн (REQUIREMENT)
Доля записей через онлайн-канал должна вырасти с 0% до 60% в течение 6 месяцев после запуска системы.
- STATUS: reviewed
- PRIORITY: must
- GOAL: доля онлайн-записей >= 60 %

### BR-003: Учёт корпоративных заказов без тетради (REQUIREMENT)
Все заказы корпоративных клиентов по договорам должны учитываться в системе вместо бумажного журнала с первого месяца после запуска.
- STATUS: reviewed
- PRIORITY: should
- GOAL: доля корпоративных заказов, учтённых в системе 100 %

## SEC-UR: Пользовательские требования (SECTION)

### UR-001: Онлайн-запись частного клиента (REQUIREMENT)
Частный клиент записывается на обслуживание через сайт без звонка администратору.
- STATUS: reviewed
- PRIORITY: must
- SCENARIO:
  1. подтверждает номер телефона кодом из SMS
  2. выбирает услугу из прайса
  3. выбирает свободное время на ближайшие 14 дней
  4. получает SMS с подтверждением записи
- Parent -> BR-002

### UR-002: Напоминание и отмена (REQUIREMENT)
Частный клиент получает напоминание о визите и может отменить запись не позднее чем за 2 часа до визита.
- STATUS: reviewed
- PRIORITY: must
- SCENARIO:
  1. получает SMS-напоминание за 24 часа до визита
  2. отвечает на SMS словом «отмена» или отменяет запись на сайте
- Parent -> BR-001

### UR-003: Корпоративные записи по договору (REQUIREMENT)
Менеджер автопарка записывает автомобили компании по договору и раз в месяц получает счёт с отсрочкой оплаты.
- STATUS: reviewed
- PRIORITY: should
- SCENARIO:
  1. входит в личный кабинет компании
  2. записывает несколько автомобилей без SMS-кода для каждой записи
  3. получает счёт за прошлый месяц
- Parent -> BR-003

### UR-004: Управление расписанием (REQUIREMENT)
Администратор видит расписание мастеров, отмечает неявки и переносит записи заболевшего мастера.
- STATUS: reviewed
- PRIORITY: must
- SCENARIO:
  1. открывает расписание на выбранный день
  2. отмечает неявку, если клиент не приехал за 15 минут
  3. переносит записи мастера, который не вышел на смену
- Parent -> BR-001
- Parent -> BR-002

## SEC-FR: Функциональные требования (SECTION)

### FR-001: Каталог услуг (REQUIREMENT)
Система должна показывать клиенту список услуг с длительностью и базовой ценой каждой услуги.
- STATUS: reviewed
- PRIORITY: must
- ACCEPTANCE: в списке есть все услуги из прайса сервиса
  для каждой услуги указаны длительность в минутах и цена в рублях
- REALIZED_BY: C4-CNT-01, ENT-02, PRC-01.T02
- Parent -> UR-001

### FR-002: Свободные слоты (REQUIREMENT)
Когда клиент выбрал услугу, система должна показать свободные слоты на 14 дней вперёд с учётом длительности услуги и смен мастеров.
- STATUS: reviewed
- PRIORITY: must
- ACCEPTANCE: показываются только слоты, в которые у мастера с нужной специализацией есть смена и нет записи
  слот не показывается, если до конца смены меньше длительности услуги
  горизонт показа — 14 календарных дней от текущей даты
- REALIZED_BY: ENT-04, ENT-08, PRC-01.T03
- Parent -> UR-001

### FR-003: Создание записи (REQUIREMENT)
Когда клиент подтвердил свободный слот, система должна создать запись со статусом «подтверждена» на мастера этого слота.
- STATUS: reviewed
- PRIORITY: must
- ACCEPTANCE: запись содержит клиента, автомобиль, услугу, мастера, дату и время начала
  закреплённый слот не показывается другим клиентам
- REALIZED_BY: C4-CNT-02, C4-CNT-03, ENT-05, PRC-01.T04, UC-01
- Parent -> UR-001

### FR-004: Подтверждение телефона (REQUIREMENT)
Система должна идентифицировать частного клиента по номеру телефона с подтверждением одноразовым кодом из SMS.
- STATUS: reviewed
- PRIORITY: must
- ACCEPTANCE: запись невозможна без введённого верного кода
  повторный вход с того же номера находит существующего клиента
- REALIZED_BY: C4-EXT-01, ENT-01, PRC-01.T01
- Parent -> UR-001

### FR-005: SMS-подтверждение записи (REQUIREMENT)
Когда запись создана, система должна отправить клиенту SMS с датой, временем и адресом сервиса.
- STATUS: reviewed
- PRIORITY: must
- ACCEPTANCE: SMS отправляется не позднее чем через 1 минуту после создания записи
- REALIZED_BY: C4-CNT-04, PRC-01.T05
- Parent -> UR-001

### FR-006: Расписание мастеров (REQUIREMENT)
Система должна показывать администратору расписание всех мастеров на выбранный день с записями и свободными слотами.
- STATUS: reviewed
- PRIORITY: must
- ACCEPTANCE: для каждого мастера видны смена, записи с клиентом и услугой, свободные интервалы
- REALIZED_BY: UC-04
- Parent -> UR-004

### FR-007: Напоминание о визите (REQUIREMENT)
За 24 часа до начала записи система должна отправить клиенту SMS-напоминание с датой, временем и адресом.
- STATUS: reviewed
- PRIORITY: must
- ACCEPTANCE: SMS уходит в интервале 24 ч ± 15 мин до начала записи
  для отменённой записи напоминание не отправляется
- REALIZED_BY: C4-CNT-04, PRC-02.T01
- Parent -> UR-002

### FR-008: Отмена записи клиентом (REQUIREMENT)
Когда клиент отменил запись не позднее чем за 2 часа до её начала, система должна перевести запись в статус «отменена».
- STATUS: reviewed
- PRIORITY: must
- ACCEPTANCE: слот отменённой записи снова показывается как свободный
  отмена позже чем за 2 часа до начала отклоняется с сообщением о сроке
- REALIZED_BY: PRC-02.T02, UC-02
- Parent -> UR-002

### FR-009: Отметка неявки (REQUIREMENT)
Если клиент не приехал в течение 15 минут после начала записи, система должна позволить администратору перевести запись в статус «неявка».
- STATUS: reviewed
- PRIORITY: must
- ACCEPTANCE: кнопка отметки неявки доступна только через 15 минут после начала записи
  запись со статусом «неявка» учитывается в доле неявок (BR-001)
- REALIZED_BY: UC-05
- Parent -> UR-004

### FR-010: Корпоративная запись (REQUIREMENT)
Система должна позволять менеджеру корпоративного клиента записывать автомобили автопарка по действующему договору без SMS-кода для каждой записи.
- STATUS: reviewed
- PRIORITY: should
- ACCEPTANCE: записать можно только автомобиль, привязанный к действующему договору
  при истёкшем договоре запись отклоняется с сообщением о сроке договора
- REALIZED_BY: ENT-03, ENT-06, UC-03
- Parent -> UR-003

### FR-011: Ежемесячный счёт (REQUIREMENT)
В первый рабочий день месяца система должна сформировать по каждому действующему договору счёт за работы прошлого месяца со сроком оплаты из договора.
- STATUS: reviewed
- PRIORITY: should
- ACCEPTANCE: в счёт попадают только записи прошлого месяца со статусом «выполнена»
  срок оплаты = дата счёта + отсрочка из договора в днях
- REALIZED_BY: ENT-07, UC-06
- Parent -> UR-003

### FR-012: Выгрузка счетов для бухгалтерии (REQUIREMENT)
Система должна выгружать счета за выбранный месяц в файл Excel (xlsx) для загрузки бухгалтером в 1С.
- STATUS: reviewed
- PRIORITY: could
- ACCEPTANCE: файл содержит номер счёта, компанию, ИНН, сумму, дату и срок оплаты
- REALIZED_BY: UC-08
- Parent -> UR-003

### FR-013: Слот занят другим клиентом (REQUIREMENT)
Если выбранный слот занял другой клиент до подтверждения записи, система должна предложить клиенту три ближайших свободных слота той же услуги.
- STATUS: reviewed
- PRIORITY: must
- ACCEPTANCE: клиент видит сообщение «Это время уже занято»
  предложенные слоты свободны на момент показа
- REALIZED_BY: PRC-01.T06
- Parent -> UR-001

### FR-014: Перенос записей мастера (REQUIREMENT)
Если мастер не вышел на смену, система должна позволить администратору перенести его записи на другого мастера той же специализации.
- STATUS: reviewed
- PRIORITY: should
- ACCEPTANCE: в списке для переноса только мастера той же специализации со свободной сменой в это время
  клиенту каждой перенесённой записи уходит SMS о смене мастера
- REALIZED_BY: UC-07
- Parent -> UR-004

## SEC-NFR: Нефункциональные требования (SECTION)

### NFR-001: Время показа свободных слотов (REQUIREMENT)
Показ свободных слотов (FR-002) должен занимать не более 2 секунд для 95% запросов при 20 одновременных пользователях.
- STATUS: reviewed
- PRIORITY: must
- METRIC: p95 времени ответа <= 2 с
- QUALITY: performance_efficiency
- Parent -> UR-001

### NFR-002: Доставка SMS-напоминаний (REQUIREMENT)
Доля доставленных SMS-напоминаний должна быть не ниже 98% за календарный месяц.
- STATUS: reviewed
- PRIORITY: must
- METRIC: доля доставленных SMS >= 98 %
- QUALITY: reliability
- Parent -> UR-002

### NFR-003: Срок действия SMS-кода (REQUIREMENT)
Одноразовый код подтверждения телефона должен действовать не более 5 минут.
- STATUS: reviewed
- PRIORITY: must
- METRIC: срок действия кода <= 5 мин
- QUALITY: security
- Parent -> UR-001

### NFR-004: Время онлайн-записи (REQUIREMENT)
Новый клиент должен завершать онлайн-запись не более чем за 3 минуты в 90% попыток.
- STATUS: reviewed
- PRIORITY: should
- METRIC: время от открытия сайта до подтверждения записи, 90-й процентиль <= 3 мин
- QUALITY: interaction_capability
- Parent -> UR-001

### NFR-005: Доступность онлайн-записи (REQUIREMENT)
Онлайн-запись должна быть доступна не менее 99,5% времени с 7:00 до 22:00 по местному времени за календарный месяц.
- STATUS: reviewed
- PRIORITY: must
- METRIC: доступность в рабочие часы >= 99.5 %
- QUALITY: reliability
- Parent -> UR-001

## SEC-CON: Ограничения (SECTION)

### CON-001: Локализация персональных данных (REQUIREMENT)
Персональные данные клиентов (ФИО, телефон, госномер автомобиля) должны храниться в базе данных на территории РФ (152-ФЗ, ст. 18, ч. 5).
- STATUS: reviewed
- CONSTRAINT_TYPE: legal

### CON-002: Бюджет первой версии (REQUIREMENT)
Стоимость разработки первой версии не должна превышать 600 000 рублей.
- STATUS: reviewed
- CONSTRAINT_TYPE: budget

### CON-003: Срок запуска (REQUIREMENT)
Онлайн-запись должна быть запущена для клиентов не позднее 1 марта 2027 года.
- STATUS: reviewed
- CONSTRAINT_TYPE: time
